string s = "";

output("ulp_output.txt"){
   // if (argc != 5 && argc != 3){
   //    dlgMessageBox("Incorrect number of arguments", "Ok");
   //    exit(1);
   // }

   // real width = strtod(argv[1]);
   // real height = strtod(argv[2]);

   // real x = 0;
   // real y = 0;
   // if (argc >= 4){
   //    x = strtod(argv[3]);
   //    y = strtod(argv[4]);
   // }

   // sprintf(s,"WIRE (%f %f) (%f %f) (%f %f) (%f %f) (%f %f)",
   //         x+width/2.0, y+height/2.0,
   //         x+width/2.0, y-height/2.0,
   //         x-width/2.0, y-height/2.0,
   //         x-width/2.0, y+height/2.0,
   //         x+width/2.0, y+height/2.0
   //         );
   system("run UCirKitCompleteScript");
}

exit(s);
