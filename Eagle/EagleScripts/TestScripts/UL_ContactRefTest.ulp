output("UL_ContactRefTest.txt"){
   schematic(SCH){
      project.board(BOARD){
         BOARD.signals(S){
            //printf("Signal '%s'\n", S.name);
            printf("\n");
            S.contactrefs(C){
               printf("%s\t,", C.element.name);
            }
         }
      }
   }
}
