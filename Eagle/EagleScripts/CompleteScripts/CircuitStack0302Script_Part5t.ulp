#include "CircuitStack0302GlobalVar.ulp"
#include "CircuitStackAddTextNumbering.ulp"

//---- Execution
output("CircuitStack0302Script_Part5t.txt"){
   addTextNumbering(leftInnerTextNumberingStartX, leftInnerTextNumberingStartY, ySpacingBetweenLargeFemaleHeaders);
   addTextNumbering(rightInnerTextNumberingStartX, rightInnerTextNumberingStartY, ySpacingBetweenLargeFemaleHeaders);
   addTextNumbering(leftOuterTextNumberingStartX, leftOuterTextNumberingStartY, ySpacingBetweenLargeFemaleHeaders);
   addTextNumbering(rightOuterTextNumberingStartX, rightOuterTextNumberingStartY, ySpacingBetweenLargeFemaleHeaders);
   // printf(commands);
}

exit(commands);
