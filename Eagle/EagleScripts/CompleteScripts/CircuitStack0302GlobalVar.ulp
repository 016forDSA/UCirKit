//*************************************************************************
//****************   Breadboard-like general information    ***************
//*************************************************************************
int numOfRows = 30;
// int numOfRows = 64;
int numOfCols = 10;

int numOfShortedFemalePinRows = numOfRows;
int numOfShortedFemalePinCols = 4;

int numOfShortedInnerPinRows = int((numOfRows+2)/8);
// int numOfShortedInnerPinRows = int(numOfRows/8);
int numOfShortedInnerPinCols = 1;

int numOfInnerPadRows = numOfRows;
int numOfInnerPadCols = numOfCols/5;

int numOfOuterPadRows = numOfRows + 2;
int numOfOuterPadCols = 1;
//*************************************************************************
//**********************  Schematic information  **************************
//*************************************************************************
real xCursor = 0;
real yCursor = 0;

int largeFemaleHeaderPartNum = 1;
string largeFemaleHeaderPartStr = "M01PTH_WITHOUT_TEXT";
real xSpacingForLargeFemaleHeader = 1.0;
real ySpacingForLargeFemaleHeader = 0.48;

int largePadPartNum = 1;
// string largePadPartStr = "M01PTH_SMD_3.25X0.85MM_NO_SILK";
string largePadPartStr = "M01PTH_SMD_3.0X1.0MM_NO_SILK";
real largePadLength = 3.0;   //change this if pad part changes
real largePadWidth = 1.0;    //change this if pad part changes
real xSpacingForLargePadPart = 1.0;
real ySpacingForLargePadPart = 0.48;

int numOfLargeFemaleContacts = numOfRows * numOfCols;

int smallFemaleHeaderPartNum = 1;
// string smallFemaleHeaderPartStr = "M01PTH_SMD_3.25X0.85MM_NO_SILK";
string smallFemaleHeaderPartStr = "M01PTH_SMD_3.0X1.0MM_NO_SILK";
real smallFemaleHeaderLength = 3.0;
real smallFemaleHeaderWidth = 1.0;
real xSpacingForSmallFemaleHeader = 1.0;
real ySpacingForSmallFemaleHeader = 0.48;

//********** Plates
int numOfRowsForHorizontalPlatesForPaper = 1;
int numOfColsForHorizontalPlatesForPaper = 1;
int numOfRowsForVerticalPlatesForPaper = 1;
int numOfColsForVerticalPlatesForPaper = 1;
int platePadForPaperPartNum = 1;
int numOfRepeatedHorizontalPlatesForPaper = 4;
int numOfRepeatedVerticalPlatesForPaper = 4;
string platePadForPaperPartStr = "M01PTH_SMD_5.1X1.4MM_NO_SILK";
real platePadForPaperLength = 5.1;  //change this if pad part changes
real platePadForPaperWidth = 1.4;   //change this if pad part changes
real xSpacingForHorizontalPlatesForPaperOnSchematics = 1.0;
real ySpacingForHorizontalPlatesForPaperOnSchematics = 0.48;
real xSpacingForVerticalPlatesForPaperOnSchematics = 1.0;
real ySpacingForVerticalPlatesForPaperOnSchematics = 0.48;

int numOfPlatesForEachHole = 2;
int platePadForHolesPartNum = 1;
string platePadForHolesPartStr = "M01PTH_SMD_5.1X1.4MM_NO_SILK";
real platePadForHolesLength = 5.1;
real platePadForHolesWidth = 1.4;
real xSpacingForPlatePadsForHoleOnSchematics = 1.0;
real ySpacingForPlatePadsForHoleOnSchematics = 0.48;

//*************************************************************************
//***************************   Board information   ***********************
//*************************************************************************

// real largeFemaleStartX = 21;  //mm
// real largeFemaleStartY = 88;  //mm

// real smallFemaleStartX = 90;   //mm
// real smallFemaleStartY = 91;   //mm

// real innerContactStartX = 124;   //mm
// real innerContactStartY = 96;    //mm

real xSpacingBetweenLargeFemaleHeaders = 2.54; //mm
real ySpacingBetweenLargeFemaleHeaders = 2.54; //mm

real xSpacingBetweenInnerContacts = 4.4;  //mm
real ySpacingBetweenInnerContacts = 2.54; //mm

real xSpacingBetweenOuterContactsForLeftAndRightZones = 4.5; //mm
real ySpacingBetweenOuterContactsForLeftAndRightZones = 2.54; //mm

real xSpacingBetweenOuterContactsForUpAndDownZones = ySpacingBetweenOuterContactsForLeftAndRightZones;
real ySpacingBetweenOuterContactsForUpAndDownZones = 4.191; //mm

real marginToVerticalBorder = 3;    //mm
real marginToTopHorizontalBorder = 2 + smallFemaleHeaderLength/2;      //mm
real marginToBottomHorizontalBorder = 2 + smallFemaleHeaderLength/2;   //mm

int numOfHoles = 4;
real holeDiameter = 4;  //mm
real holeToTopHorizontalBorder = 5;   //mm
real holeToBottomHorizontalBorder = 5;   //mm
real holeToVerticalBorder = 6;  //mm

real boardWidth;
real boardHeight;

project.board(B){
   boardWidth = u2mm(B.area.x2);
   boardHeight = u2mm(B.area.y2);
}

real largeFemaleStartX = boardWidth/2 - xSpacingBetweenLargeFemaleHeaders * (real(numOfCols)/2 + 0.5);
real largeFemaleStartY = boardHeight/2 + ySpacingBetweenLargeFemaleHeaders * (real(numOfRows)/2 - 1 + 0.5);
int largeFemaleJpStartNum = 1;
int largeFemaleJpEndNum = numOfRows * numOfCols;

real innerPadsStartX = largeFemaleStartX + 2 * xSpacingBetweenLargeFemaleHeaders;
real innerPadsStartY = largeFemaleStartY;
int innerPadsJpStartNum = largeFemaleJpEndNum + 1;
int innerPadsJpEndNum = innerPadsJpStartNum - 1 + numOfInnerPadRows * numOfInnerPadCols;

real leftOuterPadsStartX = largeFemaleStartX - 2.4 * xSpacingBetweenLargeFemaleHeaders;
real leftOuterPadsStartY = innerPadsStartY + 1 * ySpacingBetweenLargeFemaleHeaders;
int leftOuterPadsJpStartNum = innerPadsJpEndNum + 1 + numOfInnerPadRows * numOfInnerPadCols;
int leftOuterPadsJpEndNum = leftOuterPadsJpStartNum - 1 + numOfOuterPadRows * numOfOuterPadCols;

real rightOuterPadsStartX = leftOuterPadsStartX;
real rightOuterPadsStartY = leftOuterPadsStartY;
int rightOuterPadsJpStartNum = leftOuterPadsJpEndNum + 1 + numOfOuterPadRows * numOfOuterPadCols;
int rightOuterPadsJpEndNum = rightOuterPadsJpStartNum - 1 + numOfOuterPadRows * numOfOuterPadCols;

int mirror = 1;
int breadboard = 1;
int colIncrement = 1;
int rotateToVertical = 1;
int verticallySymmetric = 1;
int horizontallySymmetric = 1;

//******* plates
real horizonatalPlatePadsForPaperStartX = innerPadsStartX - largePadLength/2 + platePadForPaperLength/2 - 5.0;
real horizonatalPlatePadsForPaperStartY = innerPadsStartY + largePadWidth/2 + platePadForPaperWidth/2 + 2.0;
real xSpacingBetweenHorizontalPlatePadsForPaper = 4.0;   //mm
int horizontalPlatePadsForPaperJpStartNum = rightOuterPadsJpEndNum + numOfOuterPadRows * numOfOuterPadCols + 1;
int horizontalPlatePadsForPaperJpEndNum = horizontalPlatePadsForPaperJpStartNum - 1 + numOfRowsForHorizontalPlatesForPaper * numOfColsForHorizontalPlatesForPaper;

real verticalPlatePadsForPaperStartX = innerPadsStartX - largePadLength/2 - platePadForPaperWidth/2 - 6.0;
real verticalPlatePadsForPaperStartY = leftOuterPadsStartY - abs(smallFemaleHeaderWidth/2 - platePadForPaperLength/2);
real ySpacingBetweenVerticalPlatePadsForPaper = 4.0;   //mm
int verticalPlatePadsForPaperJpStartNum = horizontalPlatePadsForPaperJpEndNum + 1 + (numOfRepeatedHorizontalPlatesForPaper - 1) * (horizontalPlatePadsForPaperJpEndNum - horizontalPlatePadsForPaperJpStartNum + 1);
int verticalPlatePadsForPaperJpEndNum = verticalPlatePadsForPaperJpStartNum - 1 + numOfRowsForVerticalPlatesForPaper * numOfColsForVerticalPlatesForPaper;

real spacingBetweenPlateAndHole = holeDiameter/2 + platePadForHolesWidth/2 + 1.0;   //mm
int platePadsForHolesJpStartNum = verticalPlatePadsForPaperJpEndNum + 1 + (numOfRepeatedVerticalPlatesForPaper - 1) * (verticalPlatePadsForPaperJpEndNum - verticalPlatePadsForPaperJpStartNum + 1);
int platePadsForHolesJpEndNum = platePadsForHolesJpStartNum - 1 + numOfPlatesForEachHole;

//******* Fudicial Marks
string fiducialMarkPartStr = "FIDUCIAL-1X2";
real fiducialMarkToVerticalBorders = 3;   //mm
real fiducialMarkToHorizontalBorders = 3; //mm

//******* Col Shorted Female Pins
real leftShortedColFemalePinStartX = largeFemaleStartX - (real(numOfShortedFemalePinCols)/2 + 3.0) * xSpacingBetweenLargeFemaleHeaders;
real leftShortedColFemalePinStartY = largeFemaleStartY;
int leftShortedColFemalePinJpStartNum = platePadsForHolesJpEndNum + 1 + numOfPlatesForEachHole * numOfHoles * 2 - (platePadsForHolesJpEndNum - platePadsForHolesJpStartNum + 1);
int leftShortedColFemalePinJpEndNum = leftShortedColFemalePinJpStartNum + numOfShortedFemalePinRows * numOfShortedFemalePinCols/2  - 1;

real rightShortedColFemalePinStartX = leftShortedColFemalePinStartX;
real rightShortedColFemalePinStartY = leftShortedColFemalePinStartY;
int rightShortedColFemalePinJpStartNum = leftShortedColFemalePinJpEndNum + 1;
int rightShortedColFemalePinJpEndNum = rightShortedColFemalePinJpStartNum + numOfShortedFemalePinRows * numOfShortedFemalePinCols/2  - 1;

//******* Inner shorted pads
real firstShortedColInnerPinStartX = innerPadsStartX + 3.5 * xSpacingBetweenLargeFemaleHeaders;
real firstShortedColInnerPinStartY = innerPadsStartY - 1.0 * ySpacingBetweenLargeFemaleHeaders;
real secondShortedColInnerPinStartX = firstShortedColInnerPinStartX;
real secondShortedColInnerPinStartY = innerPadsStartY - 2.0 * ySpacingBetweenLargeFemaleHeaders;
real thirdShortedColInnerPinStartX = firstShortedColInnerPinStartX;
real thirdShortedColInnerPinStartY = innerPadsStartY - 3.0 * ySpacingBetweenLargeFemaleHeaders;
real fourthShortedColInnerPinStartX = firstShortedColInnerPinStartX;
real fourthShortedColInnerPinStartY = innerPadsStartY - 4.0 * ySpacingBetweenLargeFemaleHeaders;
// real ySpacingBetweenShortedInnerPads = ySpacingBetweenLargeFemaleHeaders * numOfRows / numOfShortedInnerPinRows;
real ySpacingBetweenShortedInnerPads = ySpacingBetweenLargeFemaleHeaders * 32 / numOfShortedInnerPinRows;
int shortedInnerPinJpStartNum = rightShortedColFemalePinJpEndNum + 1;
int shortedInnerPinJpEndNum = shortedInnerPinJpStartNum + numOfShortedInnerPinRows * numOfShortedInnerPinCols - 1;

//******* Text numbering
real leftInnerTextNumberingStartX = largeFemaleStartX - 1.5 * xSpacingBetweenLargeFemaleHeaders;
real leftInnerTextNumberingStartY = largeFemaleStartY;// - 0.4 * ySpacingBetweenLargeFemaleHeaders;
real rightInnerTextNumberingStartX = largeFemaleStartX + 12.5 * xSpacingBetweenLargeFemaleHeaders;
real rightInnerTextNumberingStartY = largeFemaleStartY;// -  * ySpacingBetweenLargeFemaleHeaders;

real leftOuterTextNumberingStartX = leftShortedColFemalePinStartX - 1.5 * xSpacingBetweenLargeFemaleHeaders;
real leftOuterTextNumberingStartY = largeFemaleStartY;// - 0.4 * ySpacingBetweenLargeFemaleHeaders;
real rightOuterTextNumberingStartX = (boardWidth - leftOuterTextNumberingStartX);
real rightOuterTextNumberingStartY = largeFemaleStartY;// -  * ySpacingBetweenLargeFemaleHeaders;

//*************************************************************************
//**************************  Print ***************************************
//*************************************************************************

string Fritzing_Text = "UntitledSketch3.txt";
real FritzingStartX = 1;
real FritzingStartY = 1;
int Pair_num = 0;
char c1, c2;
int x1, x2, y1, y2;
real PairX[];
real PairY[];
int Pair[];
real LeftTopStartX = 14.975;
real LeftTopStartY = 85.525;
real XSpacing = 4.45;
real YSpacing = 2.45;
//int map[] = {1, 302, 303, 304, 313, 305, 306, 307, 308, 317, 310, 301, 325, 314, 315, 324, 327, 328, 318, 316, 309, 311, 322, 333, 335, 323, 336, 338, 326, 329, 320, 312, 332, 334, 343, 344, 337, 347, 348, 339, 319, 321, 342, 345, 353, 354, 357, 358, 346, 349, 330, 331, 352, 364, 355, 365, 367, 368, 356, 359, 340, 341, 362, 405, 373, 393, 398, 388, 378, 369, 350, 351, 372, 363, 374, 403, 397, 387, 377, 379, 360, 361, 382, 383, 375, 423, 428, 408, 366, 389, 370, 371, 392, 384, 385, 415, 448, 418, 376, 399, 380, 381, 402, 394, 404, 425, 426, 396, 386, 409, 390, 391, 412, 413, 395, 435, 436, 438, 407, 419, 400, 401, 422, 414, 424, 445, 446, 406, 417, 429, 410, 411, 432, 433, 434, 455, 456, 458, 427, 439, 420, 421, 442, 443, 444, 465, 466, 416, 437, 449, 430, 431, 452, 453, 454, 475, 476, 457, 447, 459, 440, 441, 462, 463, 464, 485, 486, 467, 468, 469, 450, 451, 472, 473, 474, 495, 496, 477, 478, 479, 460, 461, 482, 483, 484, 505, 506, 487, 488, 489, 470, 471, 492, 493, 494, 515, 516, 497, 498, 499, 480, 481, 502, 503, 504, 555, 566, 507, 508, 509, 490, 491, 512, 513, 514, 563, 547, 517, 518, 519, 500, 501, 522, 523, 524, 525, 526, 527, 528, 529, 510, 511, 532, 533, 534, 564, 567, 537, 538, 539, 520, 521, 542, 543, 544, 535, 536, 558, 548, 549, 530, 531, 552, 553, 554, 545, 546, 557, 576, 559, 540, 541, 562, 565, 575, 573, 556, 568, 577, 569, 550, 551, 572, 584, 585, 574, 578, 586, 588, 579, 560, 561, 581, 592, 594, 595, 587, 598, 599, 590, 570, 571, 582, 591, 593, 583, 596, 597, 600, 589, 580};
string lines[];
int lines_count = 0;

lines[lines_count++] = "[['D', '1'], ['C', '1']]";
lines[lines_count++] = "[['D', '4'], ['B', '4']]";
lines[lines_count++] = "[['D', '6'], ['B', '6']]";
lines[lines_count++] = "[['D', '7'], ['B', '7']]";
lines[lines_count++] = "[['D', '21'], ['D', '19']]";
lines[lines_count++] = "[['D', '22'], ['D', '18']]";
lines[lines_count++] = "[['D', '23'], ['D', '17']]";
lines[lines_count++] = "[['D', '24'], ['D', '16']]";
lines[lines_count++] = "[['A', '29'], ['A', '30']]";
lines[lines_count++] = "[['A', '28'], ['A', '29']]";
lines[lines_count++] = "[['A', '27'], ['A', '28']]";
lines[lines_count++] = "[['A', '26'], ['A', '27']]";
lines[lines_count++] = "[['A', '25'], ['A', '26']]";
lines[lines_count++] = "[['A', '24'], ['A', '25']]";
lines[lines_count++] = "[['A', '23'], ['A', '24']]";
lines[lines_count++] = "[['A', '22'], ['A', '23']]";
lines[lines_count++] = "[['A', '21'], ['A', '22']]";
lines[lines_count++] = "[['D', '25'], ['D', '15']]";
lines[lines_count++] = "[['D', '26'], ['D', '14']]";
lines[lines_count++] = "[['D', '27'], ['D', '13']]";
lines[lines_count++] = "[['D', '28'], ['D', '12']]";
lines[lines_count++] = "[['D', '29'], ['D', '11']]";
lines[lines_count++] = "[['D', '30'], ['D', '10']]";
lines[lines_count++] = "[['B', '5'], ['A', '21']]";
lines[lines_count++] = "[['C', '2'], ['B', '5']]";
lines[lines_count++] = "[['J', '19'], ['G', '19']]";
lines[lines_count++] = "[['J', '18'], ['G', '18']]";
lines[lines_count++] = "[['J', '17'], ['G', '17']]";
lines[lines_count++] = "[['J', '16'], ['G', '16']]";
lines[lines_count++] = "[['J', '15'], ['G', '15']]";
lines[lines_count++] = "[['J', '14'], ['G', '14']]";
lines[lines_count++] = "[['J', '13'], ['G', '13']]";
lines[lines_count++] = "[['J', '12'], ['G', '12']]";
lines[lines_count++] = "[['J', '11'], ['G', '11']]";
lines[lines_count++] = "[['J', '10'], ['G', '10']]";
lines[lines_count++] = "[['J', '9'], ['G', '7']]";
lines[lines_count++] = "[['J', '8'], ['G', '6']]";
lines[lines_count++] = "[['J', '7'], ['G', '4']]";
lines[lines_count++] = "[['J', '6'], ['G', '1']]";
lines[lines_count++] = "[['J', '5'], ['C', '2']]";


//*************************************************************************
//**************************  Eagle Commands  *****************************
//*************************************************************************

string commands = "";
int xyz;
