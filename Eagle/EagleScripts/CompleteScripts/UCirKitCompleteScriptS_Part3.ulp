#include "UCirKitGlobalVarS.ulp"
#include "UCirKitArrangeBoard.ulp"

output("UCirKitCompleteScriptS_Part3.txt"){
   // arrangeBoard(1,
   //              numOfRows * numOfCols,
   //              colIncrement,
   //              !mirror,
   //              breadboard,
   //              !rotateToVertical,
   //              largeFemaleStartX,
   //              largeFemaleStartY,
   //              xSpacingBetweenLargeFemaleHeaders,
   //              ySpacingBetweenLargeFemaleHeaders,
   //              numOfRows,
   //              numOfCols);

   // arrangeBoard(numOfRows * numOfCols + 1,
   //              2 * numOfRows * numOfCols,
   //              colIncrement,
   //              !mirror,
   //              !breadboard,
   //              !rotateToVertical,
   //              innerContactStartX,
   //              innerContactStartY,
   //              xSpacingBetweenInnerContacts,
   //              ySpacingBetweenInnerContacts,
   //              numOfRows,
   //              numOfCols);

   // arrangeBoard(numOfRows * numOfCols + 1,
   //              2 * numOfRows * numOfCols,
   //              colIncrement,
   //              !mirror,
   //              breadboard,
   //              !rotateToVertical
   //              largeFemaleStartX,
   //              largeFemaleStartY,
   //              xSpacingBetweenLargeFemaleHeaders,
   //              ySpacingBetweenLargeFemaleHeaders,
   //              numOfRows,
   //              numOfCols);

   // arrangeBoard(2 * numOfRows * numOfCols + 1,
   //              3 * numOfRows * numOfCols,
   //              !colIncrement,
   //              !mirror,
   //              !breadboard,
   //              !rotateToVertical,
   //              smallFemaleStartX,
   //              smallFemaleStartY,
   //              xSpacingBetweenSmallFemaleHeaders,
   //              ySpacingBetweenSmallFemaleHeaders,
   //              int(2*numOfRows),
   //              int(numOfCols/2));

   // arrangeBoard(3 * numOfRows * numOfCols + 1,
   //              4 * numOfRows * numOfCols,
   //              !colIncrement,
   //              mirror,
   //              !breadboard,
   //              !rotateToVertical,
   //              smallFemaleStartX,// + numOfCols * xSpacingBetweenSmallFemaleHeaders,
   //              smallFemaleStartY,
   //              xSpacingBetweenSmallFemaleHeaders,
   //              ySpacingBetweenSmallFemaleHeaders,
   //              int(2*numOfRows),
   //              int(numOfCols/2));

   // arrangeBoard(301,
   //              600,
   //              large,
   //              !mirror);

  //  arrangeBoard(841,
  //               900,
  //               !colIncrement,
  //               !mirror,
  //               !breadboard,
  //               87,
  //               -11,
  //               4,
  //               1.6,
  //               6,
  //               10);

  // arrangeBoard(1141,
  //               1200,
  //               !colIncrement,
  //               !mirror,
  //               !breadboard,
  //               87,
  //               -11,
  //               4,
  //               1.6,
  //               6,
  //               10);

   arrangeBoard(largeFemaleJpStartNum,
                largeFemaleJpEndNum,
                colIncrement,
                !mirror,
                breadboard,
                !rotateToVertical,
                largeFemaleStartX,
                largeFemaleStartY,
                xSpacingBetweenLargeFemaleHeaders,
                ySpacingBetweenLargeFemaleHeaders,
                numOfRows,
                numOfCols);

   arrangeBoard(innerPadsJpStartNum,
                innerPadsJpEndNum,
                colIncrement,
                !mirror,
                breadboard,
                !rotateToVertical,
                largeFemaleStartX,
                largeFemaleStartY,
                xSpacingBetweenLargeFemaleHeaders,
                ySpacingBetweenLargeFemaleHeaders,
                numOfRows,
                numOfCols);

   arrangeBoard(leftOuterPadsJpStartNum,
                leftOuterPadsJpEndNum,
                !colIncrement,
                !mirror,
                !breadboard,
                !rotateToVertical,
                leftOuterPadsStartX,
                leftOuterPadsStartY,
                xSpacingBetweenOuterContactsForLeftAndRightZones,
                ySpacingBetweenOuterContactsForLeftAndRightZones,
                numOfRows * 2,
                2);

   arrangeBoard(leftOuterPadsJpStartNum + numOfRows * numOfCols,
                leftOuterPadsJpEndNum + numOfRows * numOfCols,
                !colIncrement,
                mirror,
                !breadboard,
                !rotateToVertical,
                leftOuterPadsStartX,
                leftOuterPadsStartY,
                xSpacingBetweenOuterContactsForLeftAndRightZones,
                ySpacingBetweenOuterContactsForLeftAndRightZones,
                numOfRows * 2,
                2);

   arrangeBoard(rightOuterPadsJpStartNum,
                rightOuterPadsJpEndNum,
                !colIncrement,
                !mirror,
                !breadboard,
                !rotateToVertical,
                rightOuterPadsStartX,
                rightOuterPadsStartY,
                xSpacingBetweenOuterContactsForLeftAndRightZones,
                ySpacingBetweenOuterContactsForLeftAndRightZones,
                numOfRows * 2,
                2);

   arrangeBoard(rightOuterPadsJpStartNum + numOfRows * numOfCols,
                rightOuterPadsJpEndNum + numOfRows * numOfCols,
                !colIncrement,
                mirror,
                !breadboard,
                !rotateToVertical,
                rightOuterPadsStartX,
                rightOuterPadsStartY,
                xSpacingBetweenOuterContactsForLeftAndRightZones,
                ySpacingBetweenOuterContactsForLeftAndRightZones,
                numOfRows * 2,
                2);

   arrangeBoard(upperLeftOuterPadsJpStartNum,
                upperLeftOuterPadsJpEndNum,
                colIncrement,
                !mirror,
                !breadboard,
                rotateToVertical,
                upperLeftOuterPadsStartX,
                upperLeftOuterPadsStartY,
                xSpacingBetweenOuterContactsForUpAndDownZones,
                ySpacingBetweenOuterContactsForUpAndDownZones,
                2,
                numOfCols);

   arrangeBoard(upperLeftOuterPadsJpStartNum + numOfRows * numOfCols,
                upperLeftOuterPadsJpEndNum + numOfRows * numOfCols,
                colIncrement,
                mirror,
                !breadboard,
                rotateToVertical,
                upperLeftOuterPadsStartX,
                upperLeftOuterPadsStartY,
                xSpacingBetweenOuterContactsForUpAndDownZones,
                ySpacingBetweenOuterContactsForUpAndDownZones,
                2,
                numOfCols);

   arrangeBoard(upperRightOuterPadsJpStartNum,
                upperRightOuterPadsJpEndNum,
                colIncrement,
                !mirror,
                !breadboard,
                rotateToVertical,
                upperRightOuterPadsStartX,
                upperRightOuterPadsStartY,
                xSpacingBetweenOuterContactsForUpAndDownZones,
                ySpacingBetweenOuterContactsForUpAndDownZones,
                2,
                numOfCols);

   arrangeBoard(upperRightOuterPadsJpStartNum + numOfRows * numOfCols,
                upperRightOuterPadsJpEndNum + numOfRows * numOfCols,
                colIncrement,
                mirror,
                !breadboard,
                rotateToVertical,
                upperRightOuterPadsStartX,
                upperRightOuterPadsStartY,
                xSpacingBetweenOuterContactsForUpAndDownZones,
                ySpacingBetweenOuterContactsForUpAndDownZones,
                2,
                numOfCols);

   arrangeBoard(lowerLeftOuterPadsJpStartNum,
                lowerLeftOuterPadsJpEndNum,
                colIncrement,
                !mirror,
                !breadboard,
                rotateToVertical,
                lowerLeftOuterPadsStartX,
                lowerLeftOuterPadsStartY,
                xSpacingBetweenOuterContactsForUpAndDownZones,
                ySpacingBetweenOuterContactsForUpAndDownZones,
                1,
                numOfCols);

   arrangeBoard(lowerLeftOuterPadsJpStartNum + numOfRows * numOfCols,
                lowerLeftOuterPadsJpEndNum + numOfRows * numOfCols,
                colIncrement,
                mirror,
                !breadboard,
                rotateToVertical,
                lowerLeftOuterPadsStartX,
                lowerLeftOuterPadsStartY,
                xSpacingBetweenOuterContactsForUpAndDownZones,
                ySpacingBetweenOuterContactsForUpAndDownZones,
                1,
                numOfCols);

   arrangeBoard(lowerRightOuterPadsJpStartNum,
                lowerRightOuterPadsJpEndNum,
                colIncrement,
                !mirror,
                !breadboard,
                rotateToVertical,
                lowerRightOuterPadsStartX,
                lowerRightOuterPadsStartY,
                xSpacingBetweenOuterContactsForUpAndDownZones,
                ySpacingBetweenOuterContactsForUpAndDownZones,
                1,
                numOfCols);

   arrangeBoard(lowerRightOuterPadsJpStartNum + numOfRows * numOfCols,
                lowerRightOuterPadsJpEndNum + numOfRows * numOfCols,
                colIncrement,
                mirror,
                !breadboard,
                rotateToVertical,
                lowerRightOuterPadsStartX,
                lowerRightOuterPadsStartY,
                xSpacingBetweenOuterContactsForUpAndDownZones,
                ySpacingBetweenOuterContactsForUpAndDownZones,
                1,
                numOfCols);

   // printf(commands);
}

exit(commands);
