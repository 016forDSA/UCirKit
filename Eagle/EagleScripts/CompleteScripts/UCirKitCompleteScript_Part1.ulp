#include "UCirKitGlobalVar.ulp"
#include "UCirKitAddFemaleHeaderArray.ulp"

//---- Execution
output("UCirKitCompleteScript_Part1.txt"){
   addFemaleHeaderArray(numOfRows,
                        numOfCols,
                        largeFemaleHeaderPartNum,
                        largeFemaleHeaderPartStr,
                        xSpacingForLargeFemaleHeader,
                        ySpacingForLargeFemaleHeader);

   addFemaleHeaderArray(numOfRows,
                        numOfCols,
                        smallFemaleHeaderPartNum,
                        smallFemaleHeaderPartStr,
                        xSpacingForSmallFemaleHeader,
                        ySpacingForSmallFemaleHeader);

   // addNetOnAllPins();
   // printf(commands);
}

exit(commands);
