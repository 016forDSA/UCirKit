#include "UCirKitGlobalVarS.ulp"
#include "UCirKitArrangeBoard.ulp"

// Only Bottom PCBs need to execute this!!

//---- Execution
output("UCirKitCompleteScriptS_Part4b.txt"){
   arrangeBoard(innerPadsJpStartNum,
                innerPadsJpEndNum,
                colIncrement,
                !mirror,
                !breadboard,
                !rotateToVertical,
                innerPadsStartX,
                innerPadsStartY,
                xSpacingBetweenInnerContacts,
                ySpacingBetweenInnerContacts,
                numOfRows,
                numOfCols);

   // printf(commands);
}

exit(commands);
