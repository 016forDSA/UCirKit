#include "UCirKitGlobalVarS2.ulp"
#include "UCirKitArrangeBoard.ulp"

void arrangeFemaleHeaders(){
   arrangeBoard(largeFemaleJpStartNum,
                largeFemaleJpEndNum,
                colIncrement,
                !mirror,
                breadboard,
                !rotateToVertical,
                !verticallySymmetric,
                !horizontallySymmetric,
                largeFemaleStartX,
                largeFemaleStartY,
                xSpacingBetweenLargeFemaleHeaders,
                ySpacingBetweenLargeFemaleHeaders,
                numOfRows,
                numOfCols);
}

void arrangeInnerPads(){
   arrangeBoard(innerPadsJpStartNum,
                innerPadsJpEndNum,
                colIncrement,
                !mirror,
                breadboard,
                !rotateToVertical,
                !verticallySymmetric,
                !horizontallySymmetric,
                largeFemaleStartX,
                largeFemaleStartY,
                xSpacingBetweenLargeFemaleHeaders,
                ySpacingBetweenLargeFemaleHeaders,
                numOfRows,
                numOfCols);

   arrangeBoard(innerPadsJpStartNum + numOfRows * numOfCols,
                innerPadsJpEndNum + numOfRows * numOfCols,
                colIncrement,
                mirror,
                breadboard,
                !rotateToVertical,
                !verticallySymmetric,
                !horizontallySymmetric,
                largeFemaleStartX,
                largeFemaleStartY,
                xSpacingBetweenLargeFemaleHeaders,
                ySpacingBetweenLargeFemaleHeaders,
                numOfRows,
                numOfCols);
}

void arrangeOuterPads(){
   arrangeBoard(leftOuterPadsJpStartNum,
                leftOuterPadsJpEndNum,
                !colIncrement,
                !mirror,
                !breadboard,
                !rotateToVertical,
                !verticallySymmetric,
                !horizontallySymmetric,
                leftOuterPadsStartX,
                leftOuterPadsStartY,
                xSpacingBetweenOuterContactsForLeftAndRightZones,
                ySpacingBetweenOuterContactsForLeftAndRightZones,
                numOfRows * 2,
                2);

   arrangeBoard(leftOuterPadsJpStartNum + numOfRows * numOfCols,
                leftOuterPadsJpEndNum + numOfRows * numOfCols,
                !colIncrement,
                mirror,
                !breadboard,
                !rotateToVertical,
                !verticallySymmetric,
                !horizontallySymmetric,
                leftOuterPadsStartX,
                leftOuterPadsStartY,
                xSpacingBetweenOuterContactsForLeftAndRightZones,
                ySpacingBetweenOuterContactsForLeftAndRightZones,
                numOfRows * 2,
                2);

   arrangeBoard(rightOuterPadsJpStartNum,
                rightOuterPadsJpEndNum,
                !colIncrement,
                !mirror,
                !breadboard,
                !rotateToVertical,
                !verticallySymmetric,
                !horizontallySymmetric,
                rightOuterPadsStartX,
                rightOuterPadsStartY,
                xSpacingBetweenOuterContactsForLeftAndRightZones,
                ySpacingBetweenOuterContactsForLeftAndRightZones,
                numOfRows * 2,
                2);

   arrangeBoard(rightOuterPadsJpStartNum + numOfRows * numOfCols,
                rightOuterPadsJpEndNum + numOfRows * numOfCols,
                !colIncrement,
                mirror,
                !breadboard,
                !rotateToVertical,
                !verticallySymmetric,
                !horizontallySymmetric,
                rightOuterPadsStartX,
                rightOuterPadsStartY,
                xSpacingBetweenOuterContactsForLeftAndRightZones,
                ySpacingBetweenOuterContactsForLeftAndRightZones,
                numOfRows * 2,
                2);

   arrangeBoard(upperLeftOuterPadsJpStartNum,
                upperLeftOuterPadsJpEndNum,
                colIncrement,
                !mirror,
                !breadboard,
                rotateToVertical,
                !verticallySymmetric,
                !horizontallySymmetric,
                upperLeftOuterPadsStartX,
                upperLeftOuterPadsStartY,
                xSpacingBetweenOuterContactsForUpAndDownZones,
                ySpacingBetweenOuterContactsForUpAndDownZones,
                1,
                30);

   arrangeBoard(upperLeftOuterPadsJpStartNum + numOfRows * numOfCols,
                upperLeftOuterPadsJpEndNum + numOfRows * numOfCols,
                colIncrement,
                mirror,
                !breadboard,
                rotateToVertical,
                !verticallySymmetric,
                !horizontallySymmetric,
                upperLeftOuterPadsStartX,
                upperLeftOuterPadsStartY,
                xSpacingBetweenOuterContactsForUpAndDownZones,
                ySpacingBetweenOuterContactsForUpAndDownZones,
                1,
                30);

   arrangeBoard(lowerLeftOuterPadsJpStartNum,
                lowerLeftOuterPadsJpEndNum,
                colIncrement,
                !mirror,
                !breadboard,
                rotateToVertical,
                !verticallySymmetric,
                !horizontallySymmetric,
                lowerLeftOuterPadsStartX,
                lowerLeftOuterPadsStartY,
                xSpacingBetweenOuterContactsForUpAndDownZones,
                ySpacingBetweenOuterContactsForUpAndDownZones,
                1,
                30);

   arrangeBoard(lowerLeftOuterPadsJpStartNum + numOfRows * numOfCols,
                lowerLeftOuterPadsJpEndNum + numOfRows * numOfCols,
                colIncrement,
                mirror,
                !breadboard,
                rotateToVertical,
                !verticallySymmetric,
                !horizontallySymmetric,
                lowerLeftOuterPadsStartX,
                lowerLeftOuterPadsStartY,
                xSpacingBetweenOuterContactsForUpAndDownZones,
                ySpacingBetweenOuterContactsForUpAndDownZones,
                1,
                30);
}

output("UCirKitCompleteScriptS2_Part3.txt"){
   arrangeFemaleHeaders();

   arrangeInnerPads();

   arrangeOuterPads();

   // printf(commands);
}

exit(commands);
