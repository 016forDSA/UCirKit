string add_text = "KP";
string cmd = "";
string new_name = "";
int GroupAx[], GroupBx[], GroupCx[], GroupDx[], GroupEAx[], GroupEBx[], GroupECx[], GroupEDx[];
int GroupAy[], GroupBy[], GroupCy[], GroupDy[], GroupEAy[], GroupEBy[], GroupECy[], GroupEDy[];
int GroupEAf[], GroupEBf[], GroupECf[], GroupEDf[];
string GroupAe[], GroupBe[], GroupCe[], GroupDe[], GroupEAe[], GroupEBe[], GroupECe[], GroupEDe[];
string GroupAc[], GroupBc[], GroupCc[], GroupDc[], GroupEAc[], GroupEBc[], GroupECc[], GroupEDc[];
string Renameliste[], Renamelistc[];
int Acount, Bcount, Ccount, Dcount, EAcount, EBcount, ECcount, EDcount, count, i, j, Rcount, found;
int MinDistance, TempIndex;



int TempCx, TempCy;

output("RenameNetResults.txt"){
   schematic(S) {
      project.board(BOARD){
         BOARD.signals(S){
            // printf("Signal '%s'\n", S.name);
            S.contactrefs(C){
              count++;
               TempCx = u2mil(C.contact.x);
               TempCy = u2mil(C.contact.y);
               if(TempCx >= 2380 ){ // right side
                  GroupAx[Acount] = TempCx;
                  GroupAy[Acount] = TempCy;
                  GroupAe[Acount] = C.element.name;
                  GroupAc[Acount++] = C.contact.name;
               } else if(TempCx <= 490){ // left side
                  GroupBx[Bcount] = TempCx;
                  GroupBy[Bcount] = TempCy;
                  GroupBe[Bcount] = C.element.name;
                  GroupBc[Bcount++] = C.contact.name;
               } else if((TempCx <= 1270 && TempCy >= 3500) || (TempCx <= 1270 && TempCy <= 230)){ // top side
                  GroupCx[Ccount] = TempCx;
                  GroupCy[Ccount] = TempCy;
                  GroupCe[Ccount] = C.element.name;
                  GroupCc[Ccount++] = C.contact.name;
               } else if((TempCx >= 1270 && TempCy >= 3500) || (TempCx >= 1270 && TempCy <= 230)){ // bottom side
                  GroupDx[Dcount] = TempCx;
                  GroupDy[Dcount] = TempCy;
                  GroupDe[Dcount] = C.element.name;
                  GroupDc[Dcount++] = C.contact.name;
               } else { // inner section
                  if(TempCx >= 1700){
                  GroupEAx[EAcount] = TempCx;
                  GroupEAy[EAcount] = TempCy;
                  GroupEAf[EAcount] = 1;
                  GroupEAe[EAcount] = C.element.name;
                  GroupEAc[EAcount++] = C.contact.name;
                } else if(TempCx <= 1140){
                  GroupEBx[EBcount] = TempCx;
                  GroupEBy[EBcount] = TempCy;
                  GroupEBf[EBcount] = 1;
                  GroupEBe[EBcount] = C.element.name;
                  GroupEBc[EBcount++] = C.contact.name;
                } else if(TempCx >= 1230 && TempCx <= 1240){
                  GroupECx[ECcount] = TempCx;
                  GroupECy[ECcount] = TempCy;
                  GroupECf[ECcount] = 1;
                  GroupECe[ECcount] = C.element.name;
                  GroupECc[ECcount++] = C.contact.name;
                } else if(TempCx >= 1630 && TempCx <= 1640){
                  GroupEDx[EDcount] = TempCx;
                  GroupEDy[EDcount] = TempCy;
                  GroupEDf[EDcount] = 1;
                  GroupEDe[EDcount] = C.element.name;
                  GroupEDc[EDcount++] = C.contact.name;
                }
               }
               // printf("%s,\t %s\t x = %f \t y = %f\n", C.element.name, C.contact.name, u2mil(C.contact.x), u2mil(C.contact.y));
            }

         }
      }
      printf("fuck");
      printf("%d %d %d %d %d %d %d %d %d", count, Acount, Bcount, Ccount, Dcount, EAcount, EBcount, ECcount, EDcount);
      for(i = 0; i < Acount; i++){
        found = 1;
        for(j = 0; j < EAcount && found; j++){
           // printf("%s %s %d %s %s %d\n", GroupAe[i], GroupAc[i], GroupAy[i], GroupEAe[j], GroupEAc[j], GroupEAy[j]);
            if((GroupAy[i] == (GroupEAy[j] + 21) || GroupAy[i] == (GroupEAy[j] - 29)) && GroupEAf[j]){
               GroupEAf[j] = 0;
               sprintf(Renameliste[Rcount], "%s", GroupEAe[j]);
               sprintf(Renamelistc[Rcount++], "%s", GroupEAc[j]);
               sprintf(Renameliste[Rcount], "%s", GroupAe[i]);
               sprintf(Renamelistc[Rcount++], "%s", GroupAc[i]);
               found = 0;
            }
         }
      }
      for(i = 0; i < Bcount; i++){
         found = 1;
         for(j = 0; j < EBcount && found; j++){
            if((GroupBy[i] == (GroupEBy[j] + 20) || GroupBy[i] == (GroupEBy[j] - 30)) && GroupEBf[j]){
               GroupEBf[j] = 0;
               sprintf(Renameliste[Rcount], "%s", GroupEBe[j]);
               sprintf(Renamelistc[Rcount++], "%s", GroupEBc[j]);
               sprintf(Renameliste[Rcount], "%s", GroupBe[i]);
               sprintf(Renamelistc[Rcount++], "%s", GroupBc[i]);
               found = 0;
            }
         }
      }
      for(i = 0; i < Ccount; i++){
         for(j = 0; j < ECcount; j++){
            if(GroupCy[i] <= 230){
               if(((GroupCx[i]-815)*2 + 399 ) == GroupECy[j]){
                  sprintf(Renameliste[Rcount], "%s", GroupECe[j]);
                  sprintf(Renamelistc[Rcount++], "%s", GroupECc[j]);
                  sprintf(Renameliste[Rcount], "%s", GroupCe[i]);
                  sprintf(Renamelistc[Rcount++], "%s", GroupCc[i]);
               }
            } else if(GroupCy[i] == 3520){
               if((2299 - ((GroupCx[i]-815)*2 ) == GroupECy[j])){
                  sprintf(Renameliste[Rcount], "%s", GroupECe[j]);
                  sprintf(Renamelistc[Rcount++], "%s", GroupECc[j]);
                  sprintf(Renameliste[Rcount], "%s", GroupCe[i]);
                  sprintf(Renamelistc[Rcount++], "%s", GroupCc[i]);
               }   
            } else {
               if((3299 - ((GroupCx[i]-815)*2 ) == GroupECy[j])){
                  sprintf(Renameliste[Rcount], "%s", GroupECe[j]);
                  sprintf(Renamelistc[Rcount++], "%s", GroupECc[j]);
                  sprintf(Renameliste[Rcount], "%s", GroupCe[i]);
                  sprintf(Renamelistc[Rcount++], "%s", GroupCc[i]);
               }
            }
         }
      }
      for(i = 0; i < Dcount; i++){
         for(j = 0; j < EDcount; j++){
            if(GroupDy[i] <= 230){
               if(((2058 - GroupDx[i])*2 + 399 ) == GroupEDy[j]){
                  sprintf(Renameliste[Rcount], "%s", GroupEDe[j]);
                  sprintf(Renamelistc[Rcount++], "%s", GroupEDc[j]);
                  sprintf(Renameliste[Rcount], "%s", GroupDe[i]);
                  sprintf(Renamelistc[Rcount++], "%s", GroupDc[i]);
               }
            } else if(GroupDy[i] == 3523){
               if((2299 - ((2058 - GroupDx[i])*2 ) == GroupEDy[j])){
                  sprintf(Renameliste[Rcount], "%s", GroupEDe[j]);
                  sprintf(Renamelistc[Rcount++], "%s", GroupEDc[j]);
                  sprintf(Renameliste[Rcount], "%s", GroupDe[i]);
                  sprintf(Renamelistc[Rcount++], "%s", GroupDc[i]);
               }   
            } else {
               if((3299 - ((2058 - GroupDx[i])*2 ) == GroupEDy[j])){
                  sprintf(Renameliste[Rcount], "%s", GroupEDe[j]);
                  sprintf(Renamelistc[Rcount++], "%s", GroupEDc[j]);
                  sprintf(Renameliste[Rcount], "%s", GroupDe[i]);
                  sprintf(Renamelistc[Rcount++], "%s", GroupDc[i]);
               }
            }
         }
      }
      printf("Rcount : %d\n", Rcount);

      //for(i = 0; i < Rcount; i++, count++)
      //  printf("A : %s B : %s i %d, count %d\n", Renameliste[i], Renamelistc[i], i, count);
      count = 0;
      j = 0;
      for(i = 0; i < Rcount; i+=2, count++){ 
        // printf("A : %s B : %s i %d, count %d\n", Renameliste[i], Renamelistc[i], i, count);  
        // printf("A : %s B : %s i %d, count %d\n", Renameliste[i+1], Renamelistc[i+1], i, count);
      
        S.parts(PART){
          PART.instances(INSTANCE){
            INSTANCE.gate.symbol.pins(PIN){
              if ((PART.name == Renameliste[i] /*&& PIN.name == Renamelistc[i])*/ ||
              PART.name == Renameliste[i + 1] /*&& PIN.name == Renamelistc[i + 1]*/)){
                  PIN.wires(WIRE){  
                      // printf("\t wire: (%f %f) (%f %f)\n", u2inch(WIRE.x1), u2inch(WIRE.y1), u2inch(WIRE.x2), u2inch(WIRE.y2));
                      // sprintf(new_name, "CLEAN_%d", j++);
                      // sprintf(cmd, "%s NAME %s (%f %f);", cmd, new_name, u2inch(WIRE.x1), u2inch(WIRE.y1));
                      // printf("NAME %s (%f %f)", new_name, u2inch(WIRE.x1), u2inch(WIRE.y1));
                      sprintf(new_name, "NEW_%d", count);
                      sprintf(cmd, "%s NAME %s (%f %f);", cmd, new_name, u2inch(WIRE.x1), u2inch(WIRE.y1));
                      printf("NAME %s (%f %f);\n", new_name, u2inch(WIRE.x1), u2inch(WIRE.y1));
                  }
                  //printf("JP : %s NUM %s f : %d\n", Renameliste[i], Renamelistc[i], found);
                  //found--;
              }
            }
          }
        }
      }
    }
}
exit(cmd);
