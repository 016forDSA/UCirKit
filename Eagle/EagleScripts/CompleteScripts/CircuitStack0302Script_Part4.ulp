#include "CircuitStack0302GlobalVar.ulp"
#include "CircuitStackAdd4Holes.ulp"
#include "CircuitStackAddFiducialMarksOnBothSides.ulp"

//---- Execution
output("CircuitStack0302Script_Part4.txt"){
   add4Holes();

   addFiducialMarksOnBothSides();
   // printf(commands);
}

exit(commands);
