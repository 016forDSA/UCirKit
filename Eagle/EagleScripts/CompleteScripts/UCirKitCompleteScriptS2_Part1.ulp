#include "UCirKitGlobalVarS2.ulp"
#include "UCirKitAddFemaleHeaderArray.ulp"

//---- Execution
output("UCirKitCompleteScriptS2_Part1.txt"){
   addFemaleHeaderArray(numOfRows,
                        numOfCols,
                        largeFemaleHeaderPartNum,
                        largeFemaleHeaderPartStr,
                        xSpacingForLargeFemaleHeader,
                        ySpacingForLargeFemaleHeader);

   addFemaleHeaderArray(numOfRows,
                        numOfCols,
                        largePadPartNum,
                        largePadPartStr,
                        xSpacingForLargePadPart,
                        ySpacingForLargePadPart);

   addFemaleHeaderArray(numOfRows,
                        numOfCols,
                        largePadPartNum,
                        largePadPartStr,
                        xSpacingForLargePadPart,
                        ySpacingForLargePadPart);

   addFemaleHeaderArray(numOfRows,
                        numOfCols,
                        smallFemaleHeaderPartNum,
                        smallFemaleHeaderPartStr,
                        xSpacingForSmallFemaleHeader,
                        ySpacingForSmallFemaleHeader);

   addFemaleHeaderArray(numOfRows,
                        numOfCols,
                        smallFemaleHeaderPartNum,
                        smallFemaleHeaderPartStr,
                        xSpacingForSmallFemaleHeader,
                        ySpacingForSmallFemaleHeader);

   int i;
   for (i = 0; i < numOfRepeatedHorizontalPlatesForPaper; ++i){
      addFemaleHeaderArray(numOfRowsForHorizontalPlatesForPaper,
                           numOfColsForHorizontalPlatesForPaper,
                           platePadForPaperPartNum,
                           platePadForPaperPartStr,
                           xSpacingForHorizontalPlatesForPaperOnSchematics,
                           ySpacingForHorizontalPlatesForPaperOnSchematics);
   }

   for (i = 0; i < numOfRepeatedVerticalPlatesForPaper; ++i){
      addFemaleHeaderArray(numOfRowsForVerticalPlatesForPaper,
                           numOfColsForVerticalPlatesForPaper,
                           platePadForPaperPartNum,
                           platePadForPaperPartStr,
                           xSpacingForVerticalPlatesForPaperOnSchematics,
                           ySpacingForVerticalPlatesForPaperOnSchematics);
   }

   for (i = 0; i < 2; ++i){
      addFemaleHeaderArray(numOfHoles,
                           numOfPlatesForEachHole,
                           platePadForHolesPartNum,
                           platePadForHolesPartStr,
                           xSpacingForPlatePadsForHoleOnSchematics,
                           ySpacingForPlatePadsForHoleOnSchematics);
   }
   
   // printf(commands);
}

exit(commands);
