#include "CircuitStack0302GlobalVar.ulp"
#include "UCirKitArrangeBoard.ulp"

void arrangeFemaleHeaders(){
   arrangeBoard(largeFemaleJpStartNum,
                largeFemaleJpEndNum,
                colIncrement,
                !mirror,
                breadboard,
                !rotateToVertical,
                !verticallySymmetric,
                !horizontallySymmetric,
                largeFemaleStartX,
                largeFemaleStartY,
                xSpacingBetweenLargeFemaleHeaders,
                ySpacingBetweenLargeFemaleHeaders,
                numOfRows,
                numOfCols);

   arrangeBoard(leftShortedColFemalePinJpStartNum,
                leftShortedColFemalePinJpEndNum,
                colIncrement,
                !mirror,
                !breadboard,
                !rotateToVertical,
                !verticallySymmetric,
                !horizontallySymmetric,
                leftShortedColFemalePinStartX,
                leftShortedColFemalePinStartY,
                xSpacingBetweenLargeFemaleHeaders,
                ySpacingBetweenLargeFemaleHeaders,
                numOfShortedFemalePinRows,
                numOfShortedFemalePinCols/2);

   arrangeBoard(rightShortedColFemalePinJpStartNum,
                rightShortedColFemalePinJpEndNum,
                colIncrement,
                !mirror,
                !breadboard,
                !rotateToVertical,
                verticallySymmetric,
                !horizontallySymmetric,
                rightShortedColFemalePinStartX,
                rightShortedColFemalePinStartY,
                xSpacingBetweenLargeFemaleHeaders,
                ySpacingBetweenLargeFemaleHeaders,
                numOfShortedFemalePinRows,
                numOfShortedFemalePinCols/2);
}

void arrangeInnerPads(){
   arrangeBoard(innerPadsJpStartNum,
                innerPadsJpStartNum + numOfInnerPadRows * 1 - 1,
                colIncrement,
                !mirror,
                !breadboard,
                !rotateToVertical,
                !verticallySymmetric,
                !horizontallySymmetric,
                innerPadsStartX,
                innerPadsStartY,
                xSpacingBetweenLargeFemaleHeaders,
                ySpacingBetweenLargeFemaleHeaders,
                numOfInnerPadRows,
                1);

   arrangeBoard(innerPadsJpStartNum + 1 * numOfInnerPadRows * 1,
                innerPadsJpStartNum + 2 * numOfInnerPadRows * 1 - 1,
                colIncrement,
                mirror,
                !breadboard,
                !rotateToVertical,
                !verticallySymmetric,
                !horizontallySymmetric,
                innerPadsStartX,
                innerPadsStartY,
                xSpacingBetweenLargeFemaleHeaders,
                ySpacingBetweenLargeFemaleHeaders,
                numOfInnerPadRows,
                1);

   arrangeBoard(innerPadsJpStartNum + 2 * numOfInnerPadRows * 1,
                innerPadsJpStartNum + 3 * numOfInnerPadRows * 1 - 1,
                colIncrement,
                !mirror,
                !breadboard,
                !rotateToVertical,
                verticallySymmetric,
                !horizontallySymmetric,
                innerPadsStartX,
                innerPadsStartY,
                xSpacingBetweenLargeFemaleHeaders,
                ySpacingBetweenLargeFemaleHeaders,
                numOfInnerPadRows,
                1);

   arrangeBoard(innerPadsJpStartNum + 3 * numOfInnerPadRows * 1,
                innerPadsJpStartNum + 4 * numOfInnerPadRows * 1 - 1,
                colIncrement,
                mirror,
                !breadboard,
                !rotateToVertical,
                verticallySymmetric,
                !horizontallySymmetric,
                innerPadsStartX,
                innerPadsStartY,
                xSpacingBetweenLargeFemaleHeaders,
                ySpacingBetweenLargeFemaleHeaders,
                numOfInnerPadRows,
                1);
}

void arrangeShortedInnerPads(){
   arrangeBoard(shortedInnerPinJpStartNum,
                shortedInnerPinJpEndNum,
                !colIncrement,
                !mirror,
                !breadboard,
                !rotateToVertical,
                !verticallySymmetric,
                !horizontallySymmetric,
                firstShortedColInnerPinStartX,
                firstShortedColInnerPinStartY,
                xSpacingBetweenLargeFemaleHeaders,
                ySpacingBetweenShortedInnerPads,
                numOfShortedInnerPinRows,
                numOfShortedInnerPinCols);

   arrangeBoard(shortedInnerPinJpStartNum + numOfShortedInnerPinRows * numOfShortedInnerPinCols,
                shortedInnerPinJpEndNum + numOfShortedInnerPinRows * numOfShortedInnerPinCols,
                !colIncrement,
                mirror,
                !breadboard,
                !rotateToVertical,
                !verticallySymmetric,
                !horizontallySymmetric,
                firstShortedColInnerPinStartX,
                firstShortedColInnerPinStartY,
                xSpacingBetweenLargeFemaleHeaders,
                ySpacingBetweenShortedInnerPads,
                numOfShortedInnerPinRows,
                numOfShortedInnerPinCols);

   arrangeBoard(shortedInnerPinJpStartNum + 2 * numOfShortedInnerPinRows * numOfShortedInnerPinCols,
                shortedInnerPinJpEndNum + 2 * numOfShortedInnerPinRows * numOfShortedInnerPinCols,
                !colIncrement,
                !mirror,
                !breadboard,
                !rotateToVertical,
                !verticallySymmetric,
                !horizontallySymmetric,
                secondShortedColInnerPinStartX,
                secondShortedColInnerPinStartY,
                xSpacingBetweenLargeFemaleHeaders,
                ySpacingBetweenShortedInnerPads,
                numOfShortedInnerPinRows,
                numOfShortedInnerPinCols);

   arrangeBoard(shortedInnerPinJpStartNum + 3 * numOfShortedInnerPinRows * numOfShortedInnerPinCols,
                shortedInnerPinJpEndNum + 3 * numOfShortedInnerPinRows * numOfShortedInnerPinCols,
                !colIncrement,
                mirror,
                !breadboard,
                !rotateToVertical,
                !verticallySymmetric,
                !horizontallySymmetric,
                secondShortedColInnerPinStartX,
                secondShortedColInnerPinStartY,
                xSpacingBetweenLargeFemaleHeaders,
                ySpacingBetweenShortedInnerPads,
                numOfShortedInnerPinRows,
                numOfShortedInnerPinCols);

   arrangeBoard(shortedInnerPinJpStartNum + 4 * numOfShortedInnerPinRows * numOfShortedInnerPinCols,
                shortedInnerPinJpEndNum + 4 * numOfShortedInnerPinRows * numOfShortedInnerPinCols,
                !colIncrement,
                !mirror,
                !breadboard,
                !rotateToVertical,
                !verticallySymmetric,
                !horizontallySymmetric,
                thirdShortedColInnerPinStartX,
                thirdShortedColInnerPinStartY,
                xSpacingBetweenLargeFemaleHeaders,
                ySpacingBetweenShortedInnerPads,
                numOfShortedInnerPinRows,
                numOfShortedInnerPinCols);

   arrangeBoard(shortedInnerPinJpStartNum + 5 * numOfShortedInnerPinRows * numOfShortedInnerPinCols,
                shortedInnerPinJpEndNum + 5 * numOfShortedInnerPinRows * numOfShortedInnerPinCols,
                !colIncrement,
                mirror,
                !breadboard,
                !rotateToVertical,
                !verticallySymmetric,
                !horizontallySymmetric,
                thirdShortedColInnerPinStartX,
                thirdShortedColInnerPinStartY,
                xSpacingBetweenLargeFemaleHeaders,
                ySpacingBetweenShortedInnerPads,
                numOfShortedInnerPinRows,
                numOfShortedInnerPinCols);

   arrangeBoard(shortedInnerPinJpStartNum + 6 * numOfShortedInnerPinRows * numOfShortedInnerPinCols,
                shortedInnerPinJpEndNum + 6 * numOfShortedInnerPinRows * numOfShortedInnerPinCols,
                !colIncrement,
                !mirror,
                !breadboard,
                !rotateToVertical,
                !verticallySymmetric,
                !horizontallySymmetric,
                fourthShortedColInnerPinStartX,
                fourthShortedColInnerPinStartY,
                xSpacingBetweenLargeFemaleHeaders,
                ySpacingBetweenShortedInnerPads,
                numOfShortedInnerPinRows,
                numOfShortedInnerPinCols);

   arrangeBoard(shortedInnerPinJpStartNum + 7 * numOfShortedInnerPinRows * numOfShortedInnerPinCols,
                shortedInnerPinJpEndNum + 7 * numOfShortedInnerPinRows * numOfShortedInnerPinCols,
                !colIncrement,
                mirror,
                !breadboard,
                !rotateToVertical,
                !verticallySymmetric,
                !horizontallySymmetric,
                fourthShortedColInnerPinStartX,
                fourthShortedColInnerPinStartY,
                xSpacingBetweenLargeFemaleHeaders,
                ySpacingBetweenShortedInnerPads,
                numOfShortedInnerPinRows,
                numOfShortedInnerPinCols);
}

void arrangeOuterPads(){
   arrangeBoard(leftOuterPadsJpStartNum,
                leftOuterPadsJpEndNum,
                !colIncrement,
                !mirror,
                !breadboard,
                !rotateToVertical,
                !verticallySymmetric,
                !horizontallySymmetric,
                leftOuterPadsStartX,
                leftOuterPadsStartY,
                xSpacingBetweenOuterContactsForLeftAndRightZones,
                ySpacingBetweenOuterContactsForLeftAndRightZones,
                numOfOuterPadRows,
                numOfOuterPadCols);

   arrangeBoard(leftOuterPadsJpStartNum + numOfOuterPadRows * numOfOuterPadCols,
                leftOuterPadsJpEndNum + numOfOuterPadRows * numOfOuterPadCols,
                !colIncrement,
                mirror,
                !breadboard,
                !rotateToVertical,
                !verticallySymmetric,
                !horizontallySymmetric,
                leftOuterPadsStartX,
                leftOuterPadsStartY,
                xSpacingBetweenOuterContactsForLeftAndRightZones,
                ySpacingBetweenOuterContactsForLeftAndRightZones,
                numOfOuterPadRows,
                numOfOuterPadCols);

   arrangeBoard(rightOuterPadsJpStartNum,
                rightOuterPadsJpEndNum,
                !colIncrement,
                !mirror,
                !breadboard,
                !rotateToVertical,
                verticallySymmetric,
                !horizontallySymmetric,
                rightOuterPadsStartX,
                rightOuterPadsStartY,
                xSpacingBetweenOuterContactsForLeftAndRightZones,
                ySpacingBetweenOuterContactsForLeftAndRightZones,
                numOfOuterPadRows,
                numOfOuterPadCols);

   arrangeBoard(rightOuterPadsJpStartNum + numOfOuterPadRows * numOfOuterPadCols,
                rightOuterPadsJpEndNum + numOfOuterPadRows * numOfOuterPadCols,
                !colIncrement,
                mirror,
                !breadboard,
                !rotateToVertical,
                verticallySymmetric,
                !horizontallySymmetric,
                rightOuterPadsStartX,
                rightOuterPadsStartY,
                xSpacingBetweenOuterContactsForLeftAndRightZones,
                ySpacingBetweenOuterContactsForLeftAndRightZones,
                numOfOuterPadRows,
                numOfOuterPadCols);

}

output("CircuitStack0302Script_Part3.txt"){
   arrangeFemaleHeaders();

   arrangeInnerPads();

   arrangeOuterPads();

   arrangeShortedInnerPads();

   printf("largeFemaleJpStartNum : %d\n", largeFemaleJpStartNum);
   printf("largeFemaleJpEndNum : %d\n", largeFemaleJpEndNum);
   printf("innerPadsJpStartNum : %d\n", innerPadsJpStartNum);
   printf("innerPadsJpEndNum : %d\n", innerPadsJpEndNum);
   printf("leftOuterPadsJpStartNum : %d\n", leftOuterPadsJpStartNum);
   printf("leftOuterPadsJpEndNum : %d\n", leftOuterPadsJpEndNum);
   printf("rightOuterPadsJpStartNum : %d\n", rightOuterPadsJpStartNum);
   printf("rightOuterPadsJpEndNum : %d\n", rightOuterPadsJpEndNum);
   printf("horizontalPlatePadsForPaperJpStartNum : %d\n", horizontalPlatePadsForPaperJpStartNum);
   printf("horizontalPlatePadsForPaperJpEndNum : %d\n", horizontalPlatePadsForPaperJpEndNum);
   printf("verticalPlatePadsForPaperJpStartNum : %d\n", verticalPlatePadsForPaperJpStartNum);
   printf("verticalPlatePadsForPaperJpEndNum : %d\n", verticalPlatePadsForPaperJpEndNum);
   printf("platePadsForHolesJpStartNum : %d\n", platePadsForHolesJpStartNum);
   printf("platePadsForHolesJpEndNum : %d\n", platePadsForHolesJpEndNum);
   printf("leftShortedColFemalePinJpStartNum : %d\n", leftShortedColFemalePinJpStartNum);
   printf("leftShortedColFemalePinJpEndNum : %d\n", leftShortedColFemalePinJpEndNum);
   printf("rightShortedColFemalePinJpStartNum : %d\n", rightShortedColFemalePinJpStartNum);
   printf("rightShortedColFemalePinJpEndNum : %d\n", rightShortedColFemalePinJpEndNum);
   printf("shortedInnerPinJpStartNum : %d\n", shortedInnerPinJpStartNum);
   printf("shortedInnerPinJpEndNum : %d\n", shortedInnerPinJpEndNum);
   printf("shortedInnerPinJpStartNum + numOfShortedInnerPinRows * numOfShortedInnerPinCols : %d\n", shortedInnerPinJpStartNum + numOfShortedInnerPinRows * numOfShortedInnerPinCols);
   printf("shortedInnerPinJpEndNum + numOfShortedInnerPinRows * numOfShortedInnerPinCols : %d\n", shortedInnerPinJpEndNum + numOfShortedInnerPinRows * numOfShortedInnerPinCols);
}

exit(commands);
