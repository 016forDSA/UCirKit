#include "UCirKitGlobalVarS2.ulp"
#include "UCirKitArrangeBoard.ulp"

// Only Bottom PCBs need to execute this!!

//---- Execution
output("UCirKitCompleteScriptS2_Part4b.txt"){
   arrangeBoard(innerPadsJpStartNum,
                innerPadsJpEndNum,
                colIncrement,
                !mirror,
                !breadboard,
                !rotateToVertical,
                !verticallySymmetric,
                !horizontallySymmetric,
                innerPadsStartX,
                innerPadsStartY,
                xSpacingBetweenInnerContacts,
                ySpacingBetweenInnerContacts,
                numOfRows,
                numOfCols);

   arrangeBoard(innerPadsJpStartNum + numOfRows * numOfCols,
                innerPadsJpEndNum + numOfRows * numOfCols,
                colIncrement,
                !mirror,
                !breadboard,
                !rotateToVertical,
                !verticallySymmetric,
                !horizontallySymmetric,
                innerPadsStartX,
                innerPadsStartY,
                xSpacingBetweenInnerContacts,
                ySpacingBetweenInnerContacts,
                numOfRows,
                numOfCols);

   arrangeBoard(horizontalPlatePadsForPaperJpStartNum,
                horizontalPlatePadsForPaperJpEndNum,
                colIncrement,
                !mirror,
                !breadboard,
                !rotateToVertical,
                !verticallySymmetric,
                !horizontallySymmetric,
                horizonatalPlatePadsForPaperStartX,
                horizonatalPlatePadsForPaperStartY,
                xSpacingBetweenHorizontalPlatePadsForPaper,
                0,
                numOfRowsForHorizontalPlatesForPaper,
                numOfColsForHorizontalPlatesForPaper);

   arrangeBoard(horizontalPlatePadsForPaperJpStartNum + numOfRowsForHorizontalPlatesForPaper * numOfColsForHorizontalPlatesForPaper,
                horizontalPlatePadsForPaperJpEndNum + numOfRowsForHorizontalPlatesForPaper * numOfColsForHorizontalPlatesForPaper,
                colIncrement,
                !mirror,
                !breadboard,
                !rotateToVertical,
                verticallySymmetric,
                horizontallySymmetric,
                horizonatalPlatePadsForPaperStartX,
                horizonatalPlatePadsForPaperStartY,
                xSpacingBetweenHorizontalPlatePadsForPaper,
                0,
                numOfRowsForHorizontalPlatesForPaper,
                numOfColsForHorizontalPlatesForPaper);

   arrangeBoard(horizontalPlatePadsForPaperJpStartNum + 2 * numOfRowsForHorizontalPlatesForPaper * numOfColsForHorizontalPlatesForPaper,
                horizontalPlatePadsForPaperJpEndNum + 2 * numOfRowsForHorizontalPlatesForPaper * numOfColsForHorizontalPlatesForPaper,
                colIncrement,
                mirror,
                !breadboard,
                !rotateToVertical,
                verticallySymmetric,
                !horizontallySymmetric,
                horizonatalPlatePadsForPaperStartX,
                horizonatalPlatePadsForPaperStartY,
                xSpacingBetweenHorizontalPlatePadsForPaper,
                0,
                numOfRowsForHorizontalPlatesForPaper,
                numOfColsForHorizontalPlatesForPaper);

   arrangeBoard(horizontalPlatePadsForPaperJpStartNum + 3 * numOfRowsForHorizontalPlatesForPaper * numOfColsForHorizontalPlatesForPaper,
                horizontalPlatePadsForPaperJpEndNum + 3 * numOfRowsForHorizontalPlatesForPaper * numOfColsForHorizontalPlatesForPaper,
                colIncrement,
                mirror,
                !breadboard,
                !rotateToVertical,
                !verticallySymmetric,
                horizontallySymmetric,
                horizonatalPlatePadsForPaperStartX,
                horizonatalPlatePadsForPaperStartY,
                xSpacingBetweenHorizontalPlatePadsForPaper,
                0,
                numOfRowsForHorizontalPlatesForPaper,
                numOfColsForHorizontalPlatesForPaper);

   arrangeBoard(verticalPlatePadsForPaperJpStartNum,
                verticalPlatePadsForPaperJpEndNum,
                !colIncrement,
                !mirror,
                !breadboard,
                rotateToVertical,
                !verticallySymmetric,
                !horizontallySymmetric,
                verticalPlatePadsForPaperStartX,
                verticalPlatePadsForPaperStartY,
                0,
                ySpacingBetweenVerticalPlatePadsForPaper,
                numOfRowsForVerticalPlatesForPaper,
                numOfColsForVerticalPlatesForPaper);

   arrangeBoard(verticalPlatePadsForPaperJpStartNum + numOfRowsForVerticalPlatesForPaper * numOfColsForVerticalPlatesForPaper,
                verticalPlatePadsForPaperJpEndNum + numOfRowsForVerticalPlatesForPaper * numOfColsForVerticalPlatesForPaper,
                !colIncrement,
                !mirror,
                !breadboard,
                rotateToVertical,
                verticallySymmetric,
                horizontallySymmetric,
                verticalPlatePadsForPaperStartX,
                verticalPlatePadsForPaperStartY,
                0,
                ySpacingBetweenVerticalPlatePadsForPaper,
                numOfRowsForVerticalPlatesForPaper,
                numOfColsForVerticalPlatesForPaper);

   arrangeBoard(verticalPlatePadsForPaperJpStartNum + 2 * numOfRowsForVerticalPlatesForPaper * numOfColsForVerticalPlatesForPaper,
                verticalPlatePadsForPaperJpEndNum + 2 * numOfRowsForVerticalPlatesForPaper * numOfColsForVerticalPlatesForPaper,
                !colIncrement,
                mirror,
                !breadboard,
                rotateToVertical,
                verticallySymmetric,
                !horizontallySymmetric,
                verticalPlatePadsForPaperStartX,
                verticalPlatePadsForPaperStartY,
                0,
                ySpacingBetweenVerticalPlatePadsForPaper,
                numOfRowsForVerticalPlatesForPaper,
                numOfColsForVerticalPlatesForPaper);

   arrangeBoard(verticalPlatePadsForPaperJpStartNum + 3 * numOfRowsForVerticalPlatesForPaper * numOfColsForVerticalPlatesForPaper,
                verticalPlatePadsForPaperJpEndNum + 3 * numOfRowsForVerticalPlatesForPaper * numOfColsForVerticalPlatesForPaper,
                !colIncrement,
                mirror,
                !breadboard,
                rotateToVertical,
                !verticallySymmetric,
                horizontallySymmetric,
                verticalPlatePadsForPaperStartX,
                verticalPlatePadsForPaperStartY,
                0,
                ySpacingBetweenVerticalPlatePadsForPaper,
                numOfRowsForVerticalPlatesForPaper,
                numOfColsForVerticalPlatesForPaper);

   for (int i = 0; i < numOfHoles * numOfPlatesForEachHole * 2; i = i + 2){
      int verticallySymmetricBit = int(i/2) % 2;
      int horizontallySymmetricBit = int(i/4) % 2;
      int mirrorBit = int(i/8) % 2;

      arrangeBoard(platePadsForHolesJpStartNum + i,
                   platePadsForHolesJpStartNum + i,
                   colIncrement,
                   mirrorBit,
                   !breadboard,
                   !rotateToVertical,
                   verticallySymmetricBit,
                   horizontallySymmetricBit,
                   holeToVerticalBorder,
                   holeToBottomHorizontalBorder + spacingBetweenPlateAndHole,
                   0,
                   0,
                   1,
                   1);

      arrangeBoard(platePadsForHolesJpStartNum + 1 + i,
                   platePadsForHolesJpStartNum + 1 + i,
                   colIncrement,
                   mirrorBit,
                   !breadboard,
                   rotateToVertical,
                   verticallySymmetricBit,
                   horizontallySymmetricBit,
                   holeToVerticalBorder + spacingBetweenPlateAndHole,
                   holeToBottomHorizontalBorder,
                   0,
                   0,
                   1,
                   1);
      // printf("platePadsForHolesJpStartNum + i = %d; \t v %d \t h %d \t m %d\n", platePadsForHolesJpStartNum + i, verticallySymmetricBit, horizontallySymmetricBit, mirrorBit);
      // printf("platePadsForHolesJpStartNum + i + 1 = %d; \t v %d \t h %d \t m %d\n", platePadsForHolesJpStartNum + i + 1, verticallySymmetricBit, horizontallySymmetricBit, mirrorBit);
   }
   // printf(commands);
}

exit(commands);
