#include "CircuitStack0302GlobalVar.ulp"
#include "CircuitStackAddNetOnAllPins.ulp"

//---- Execution
output("CircuitStack0302Script_Part2.txt"){
   addNetOnAllPins();

   // printf(commands);
}

exit(commands);
