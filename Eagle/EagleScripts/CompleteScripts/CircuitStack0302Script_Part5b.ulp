#include "CircuitStack0302GlobalVar.ulp"
#include "UCirKitConnectTopBottomPads.ulp"


//---- Execution
output("CircuitStack0302Script_Part5b.txt"){
   connectTopBottomPads(numOfRows * numOfCols + 1, 2 * numOfRows * numOfCols + 1);
   connectTopBottomPads(3 * numOfRows * numOfCols + 1, 4 * numOfRows * numOfCols + 1);

   // printf(commands);
}

exit(commands);
