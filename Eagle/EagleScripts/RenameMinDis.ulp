string add_text = "KP";
string cmd = "";
string new_name = "";
int GroupAx[], GroupBx[], GroupCx[], GroupDx[], GroupEx[];
int GroupAy[], GroupBy[], GroupCy[], GroupDy[], GroupEy[];
int GroupAf[], GroupBf[], GroupCf[], GroupDf[], GroupEf[];
string GroupAe[], GroupBe[], GroupCe[], GroupDe[], GroupEe[];
string GroupAc[], GroupBc[], GroupCc[], GroupDc[], GroupEc[];
string Renameliste[], Renamelistc[];
int Acount, Bcount, Ccount, Dcount, Ecount, count, i, j, Rcount, found;
int MinDistance, TempIndex;


int TempCx, TempCy, TempDistance;
real distance(int a, int b, int c, int d){
   return (abs(a - b) ^ 2 + abs(c - d) ^ 2) ^ (1/2);
}
output("RenameNetResults.txt"){
   schematic(S) {
      project.board(BOARD){
         BOARD.signals(S){
            // printf("Signal '%s'\n", S.name);
            S.contactrefs(C){
              count++;
               TempCx = u2mil(C.contact.x);
               TempCy = u2mil(C.contact.y);
               if(TempCx >= 2500){ // right side
                  GroupAx[Acount] = TempCx;
                  GroupAy[Acount] = TempCy;
                  GroupAf[Acount] = 1;
                  GroupAe[Acount] = C.element.name;
                  GroupAc[Acount++] = C.contact.name;
               } else if(TempCx <= 400){ // left side
                  GroupBx[Bcount] = TempCx;
                  GroupBy[Bcount] = TempCy;
                  GroupBf[Bcount] = 1;
                  GroupBe[Bcount] = C.element.name;
                  GroupBc[Bcount++] = C.contact.name;
               } else if(TempCy >= 3500){ // top side
                  GroupCx[Ccount] = TempCx;
                  GroupCy[Ccount] = TempCy;
                  GroupCf[Ccount] = 1;
                  GroupCe[Ccount] = C.element.name;
                  GroupCc[Ccount++] = C.contact.name;
               } else if(TempCy <= 400){ // bottom side
                  GroupDx[Dcount] = TempCx;
                  GroupDy[Dcount] = TempCy;
                  GroupDf[Dcount] = 1;
                  GroupDe[Dcount] = C.element.name;
                  GroupDc[Dcount++] = C.contact.name;
               } else { // inner section
                  GroupEx[Ecount] = TempCx;
                  GroupEy[Ecount] = TempCy;
                  GroupEf[Ecount] = 1;
                  GroupEe[Ecount] = C.element.name;
                  GroupEc[Ecount++] = C.contact.name;
               }
               // printf("%s,\t %s\t x = %f \t y = %f\n", C.element.name, C.contact.name, u2mil(C.contact.x), u2mil(C.contact.y));
            }

         }
      }
      printf("%d %d %d %d %d %d", count, Acount, Bcount, Ccount, Dcount, Ecount);
      for(i = 0; i < Acount; i++){
        MinDistance = 100000000;
        TempIndex = 0;
        found = 1;
        for(j = 0; j < Ecount && found; j++){
            TempDistance = distance(GroupAx[i], GroupAy[i], GroupEx[j], GroupEy[j]);
            if(MinDistance >= TempDistance && GroupEf[j]){
               MinDistance = TempDistance;
               TempIndex = j;
            }
            if(TempDistance <= 400 && GroupEf[j]){
               GroupEf[j] = 0;
               sprintf(Renameliste[Rcount], "%s", GroupEe[j]);
               sprintf(Renamelistc[Rcount++], "%s", GroupEc[j]);
               sprintf(Renameliste[Rcount], "%s", GroupAe[i]);
               sprintf(Renamelistc[Rcount++], "%s", GroupAc[i]);
               found = 0;
            }
         }
         if(found){
            GroupEf[TempIndex] = 0;
            sprintf(Renameliste[Rcount], "%s", GroupEe[TempIndex]);
            sprintf(Renamelistc[Rcount++], "%s", GroupEc[TempIndex]);
            sprintf(Renameliste[Rcount], "%s", GroupAe[i]);
            sprintf(Renamelistc[Rcount++], "%s", GroupAc[i]);
            found = 0;
          }
        }
        for(i = 0; i < Bcount; i++){
         MinDistance = 100000000;
         TempIndex = 0;
         found = 1;
         for(j = 0; j < Ecount && found; j++){
            TempDistance = distance(GroupBx[i], GroupBy[i], GroupEx[j], GroupEy[j]);
            if(MinDistance >= TempDistance && GroupEf[j]){
               MinDistance = TempDistance;
               TempIndex = j;
            }
            if(TempDistance <= 400 && GroupEf[j]){
                GroupEf[j] = 0;
                sprintf(Renameliste[Rcount], "%s", GroupEe[j]);
                sprintf(Renamelistc[Rcount++], "%s", GroupEc[j]);
                sprintf(Renameliste[Rcount], "%s", GroupBe[i]);
                sprintf(Renamelistc[Rcount++], "%s", GroupBc[i]);
                found = 0;
            }
         }
         if(found){
            GroupEf[TempIndex] = 0;
            sprintf(Renameliste[Rcount], "%s", GroupEe[TempIndex]);
            sprintf(Renamelistc[Rcount++], "%s", GroupEc[TempIndex]);
            sprintf(Renameliste[Rcount], "%s", GroupBe[i]);
            sprintf(Renamelistc[Rcount++], "%s", GroupBc[i]);
            found = 0;
          }
      }
      for(i = 0; i < Ccount; i++){

         MinDistance = 100000000;
         TempIndex = 0;
         found = 1;
         for(j = 0; j < Ecount && found; j++){
            TempDistance = distance(GroupCx[i], GroupCy[i], GroupEx[j], GroupEy[j]);
            if(MinDistance >= TempDistance && GroupEf[j]){
               MinDistance = TempDistance;
               TempIndex = j;
            }
            if(TempDistance <= 600 && GroupEf[j]){
                GroupEf[j] = 0;
                sprintf(Renameliste[Rcount], "%s", GroupEe[j]);
                sprintf(Renamelistc[Rcount++], "%s", GroupEc[j]);
                sprintf(Renameliste[Rcount], "%s", GroupCe[i]);
                sprintf(Renamelistc[Rcount++], "%s", GroupCc[i]);
                found = 0;
            }
          }
          if(found){
            GroupEf[TempIndex] = 0;
            sprintf(Renameliste[Rcount], "%s", GroupEe[TempIndex]);
            sprintf(Renamelistc[Rcount++], "%s", GroupEc[TempIndex]);
            sprintf(Renameliste[Rcount], "%s", GroupCe[i]);
            sprintf(Renamelistc[Rcount++], "%s", GroupCc[i]);
            found = 0;
          }
        }
        for(i = 0; i < Dcount; i++){
         MinDistance = 100000000;
         TempIndex = 0;
         found = 1;
         for(j = 0; j < Ecount && found; j++){
            TempDistance = distance(GroupDx[i], GroupDy[i], GroupEx[j], GroupEy[j]);
            if(MinDistance >= TempDistance && GroupEf[j]){
               MinDistance = TempDistance;
               TempIndex = j;
            }
            if(TempDistance <= 600 && GroupEf[j]){
                GroupEf[j] = 0;
                sprintf(Renameliste[Rcount], "%s", GroupEe[j]);
                sprintf(Renamelistc[Rcount++], "%s", GroupEc[j]);
                sprintf(Renameliste[Rcount], "%s", GroupDe[i]);
                sprintf(Renamelistc[Rcount++], "%s", GroupDc[i]);
                found = 0;
            }
         }
         if(found){
            GroupEf[TempIndex] = 0;
            sprintf(Renameliste[Rcount], "%s", GroupEe[TempIndex]);
            sprintf(Renamelistc[Rcount++], "%s", GroupEc[TempIndex]);
            sprintf(Renameliste[Rcount], "%s", GroupDe[i]);
            sprintf(Renamelistc[Rcount++], "%s", GroupDc[i]);
            found = 0;
          }
      }
      printf("Rcount : %d\n", Rcount);
      //for(i = 0; i < Rcount; i++, count++)
      //  printf("A : %s B : %s i %d, count %d\n", Renameliste[i], Renamelistc[i], i, count);
      count = 0;
      for(i = 0; i < Rcount; i+=2, count++){
      // printf("A : %s B : %s i %d, count %d\n", Renameliste[i], Renamelistc[i], i, count);  
      // printf("A : %s B : %s i %d, count %d\n", Renameliste[i+1], Renamelistc[i+1], i, count);
      S.parts(PART){
         PART.instances(INSTANCE){
            INSTANCE.gate.symbol.pins(PIN){
                  if ((PART.name == Renameliste[i] && PIN.name == Renamelistc[i]) ||
                   (PART.name == Renameliste[i + 1] && PIN.name == Renamelistc[i + 1])){
                     PIN.wires(WIRE){  
                        // printf("\t wire: (%f %f) (%f %f)\n", u2inch(WIRE.x1), u2inch(WIRE.y1), u2inch(WIRE.x2), u2inch(WIRE.y2));
                        sprintf(new_name, "NEW_%d", count);
                        sprintf(cmd, "%s NAME %s (%f %f);", cmd, new_name, u2inch(WIRE.x1), u2inch(WIRE.y1));
                        printf("NAME %s (%f %f);\n", new_name, u2inch(WIRE.x1), u2inch(WIRE.y1));
                     }
                     //printf("JP : %s NUM %s f : %d\n", Renameliste[i], Renamelistc[i], found);
                     //found--;
                   }
                }
            }
          }
        }
      }
}
